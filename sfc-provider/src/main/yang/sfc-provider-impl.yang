// vi: set smarttab et sw=4 tabstop=4:
module sfc-provider-impl {

  yang-version 1;
  namespace "urn:opendaylight:params:xml:ns:yang:controller:config:sfc-provider:impl";
  prefix "sfc-provider-impl";

  import config { prefix config; revision-date 2013-04-05; }
  import rpc-context { prefix rpcx; revision-date 2013-06-17; }
  import opendaylight-md-sal-binding {
    prefix mdsal;
    revision-date 2013-10-28;
  }

  organization "Cisco Systems, Inc.";
  contact "Reinaldo Penno <repenno@cisco.com>";

  description
    "This module contains the base YANG definitions for
     sfc-provider impl implementation.";

  revision "2014-06-30" {
    description "Initial revision.";
    reference "https://tools.ietf.org/html/draft-penno-sfc-yang";
  }

  identity sfc-provider-impl {
    base config:module-type;
    description
      "This is the definition of the service implementation" +
      "as a module identity";

      // Specifies the prefix for generated java classes.
      config:java-name-prefix SfcProvider;
  }

  augment "/config:modules/config:module/config:configuration" {
    description
      "Augments the 'configuration' choice node under
       modules/module.";
    case sfc-provider-impl {
      when "/config:modules/config:module/config:type =
        'sfc-provider-impl'";

      container data-broker {
        description
          "wires in the data broker registry service";
        uses config:service-ref {
          refine type {
            mandatory false;
            config:required-identity mdsal:binding-async-data-broker;
          }
        }
      }

      container binding-registry {
        description
          "wires in the binding broker osgi service";
        uses config:service-ref {
          refine type {
            mandatory true;
            config:required-identity
              mdsal:binding-broker-osgi-registry;
          }
        }
      }

      container rpc-registry {
        description
          "wires in the RPC registry service";
        uses config:service-ref {
          refine type {
             mandatory true;
             config:required-identity mdsal:binding-rpc-registry;
          }
        }
      }
    }
  }
}
